(defun c:MLF (/ ss i ent)
	(SETQ rad (getreal "\Enter Radius: "))
	(setq ss (ssget '((0 . "LWPOLYLINE"))))
	(setq i 0)
	(command "FILLET" "R" rad)
	(while (< i (sslength ss))
		(setq ent (ssname ss i))
		(command "FILLET" "P" ent)
		(setq i (1+ i))
	)
	(princ)
)
